module exampleapp-impl {
    yang-version 1;
    namespace "urn:opendaylight:params:xml:ns:yang:exampleapp:impl";
    prefix "exampleapp-impl";

    import config { prefix config; revision-date 2013-04-05; }
    import opendaylight-md-sal-binding { prefix md-sal-binding; revision-date 2013-10-28;}

    description
        "Service definition for exampleapp project";

    revision "2016-03-28" {
        description
            "Initial revision";
    }

    identity exampleapp {
        base config:module-type;
        config:java-name-prefix Exampleapp;
    }

    augment "/config:modules/config:module/config:configuration" {
        case exampleapp {
            when "/config:modules/config:module/config:type = 'exampleapp'";
            container broker {
                uses config:service-ref {
                    refine type {
                        mandatory true;
                        config:required-identity md-sal-binding:binding-broker-osgi-registry;
                    }
                }
            }
           //Wires dependent services into this class - in this case the RPC registry service
           container rpc-registry {
               uses config:service-ref {
                   refine type {
                       mandatory true;
                       config:required-identity md-sal-binding:binding-rpc-registry;
                   }
               }
           } 
        }
    }
}
