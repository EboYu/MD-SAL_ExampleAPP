module ebo-rpcprovider {
  yang-version 1;
  namespace "urn:opendaylight:sdnebo:rpcprovider";
  prefix provider;

  import ietf-inet-types {
    prefix inet;
    revision-date 2010-09-24;
  }

  description "Model definition for sdnebo ebo-rpcprovider.";

  revision 2016-03-26 {
    description "Initial revision of ebo-rpcprovider.";
  }

  typedef keyword-type {
    type string {
      length "1 .. 8";
      pattern "[a-zA-Z]*";
    }
  }

  grouping profile {

    leaf city {
      type string;
    }

    leaf employees {
      type uint32;
    }
  }

  rpc ebo-rpcprovider {

    input {
      leaf keyword {
        type keyword-type;
      }
    }

    output {

      leaf url {
        type inet:uri;
      }

      leaf email {
        type string;
      }

      uses profile;
    }
  }
}
