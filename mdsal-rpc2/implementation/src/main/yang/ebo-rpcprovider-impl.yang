module ebo-rpcprovider-impl {
  yang-version 1;
  namespace "urn:opendaylight:sdnebo:ebo:rpcprovider-impl";
  prefix ebo-rpcprovider-impl;

  import config {
    prefix config;
    revision-date 2013-04-05;
  }

  import opendaylight-md-sal-binding {
    prefix md-sal;
    revision-date 2013-10-28;
  }

  description "Definition of sdnebo :: ebo :: rpcprovider-impl";

  revision 2016-03-26 {
    description "Initial revision";
  }

  identity ebo-rpcprovider-impl {
    base config:module-type;
    config:java-name-prefix EboRpcProvider;
  }

  augment "/config:modules/config:module/config:configuration" {
    case ebo-rpcprovider-impl {
      when "/config:modules/config:module/config:type = 'ebo-rpcprovider-impl'";

      container rpc-registry {
        uses config:service-ref {
          refine type {
            mandatory false;
            config:required-identity md-sal:binding-rpc-registry;
          }
        }
      }
      
      leaf contents-switch-flag {
        type string;
      }
    }
  }
}
